/* --------------------------------------------------------------------------
*
* (C) Copyright …
*
* ---------------------------------------------------------------------------
*/

/*!
 * @file PointCloud3D.asn
 * @date 01/12/2017
 * @author Alessandro Bianco
 */

/*!
 * @addtogroup BaseTypes
 * 
 * Specification of PointCloud3D.
 * 
 * 
 * @{
 */
PointCloud3DNS DEFINITIONS ::=
BEGIN

PointCloud3DMode ::= ENUMERATED 
	{
	base-mode,
	with-normals
	}

PointCloud3D ::= SEQUENCE
	{
	point-cloud-time		INTEGER,
	frame-identifier		T61String,
	data				SEQUENCE OF REAL,
	size				INTEGER,
	point-cloud-mode		PointCloud3DMode
	}

END

/** @} */
