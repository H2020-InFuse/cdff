/* --------------------------------------------------------------------------
*
* (C) Copyright …
*
* ---------------------------------------------------------------------------
*/

/*!
 * @file VisualPointFeatureVector3D.asn
 * @date 08/12/2017
 * @author Alessandro Bianco
 *
 */

/*!
 * @addtogroup BaseTypes
 * 
 * Specification of the VisualPointFeatureVector class.
 * 
 * 
 * @{
 */
VisualPointFeature3DNS DEFINITIONS ::=
BEGIN

IMPORTS
Point3D FROM GeometryNS
T-Int32, T-UInt32, T-Int8, T-UInt8, T-Boolean  FROM TASTE-BasicTypes 
T-Int64, T-UInt16, T-Double, T-Float, T-UInt64, T-String FROM TASTE-ExtendedTypes;

-- Max. number of features
features3DElementsMax T-UInt32 ::= 51200

-- Max. name size
descriptor3DNameLength T-UInt32 ::= 352

Point3DReference ::= SEQUENCE
	{
	pointCloudIdentifier	T-UInt16,
	index 			T-UInt64
	}

VisualPointFeature3D ::= SEQUENCE
	{
	point		CHOICE { position Point3D, reference Point3DReference },
	descriptor	SEQUENCE (SIZE(0..descriptor3DNameLength)) OF T-Float
	}

VisualPointFeatureVector3DType ::= ENUMERATED
	{
	all-positions	(0),
	all-references	(1),
	hybrid-vector	(2)
	}

VisualPointFeatureVector3D ::= SEQUENCE
	{
	list		SEQUENCE (SIZE(0..features3DElementsMax)) OF VisualPointFeature3D,
	list-type	VisualPointFeatureVector3DType
	}
END
