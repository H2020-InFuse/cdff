/*!
 * @file ImageType.asn
 * @date 15/11/2017
 * @author Alessandro Bianco
 * @changes 5/12/2017 - xma- dynamic to static allocation
 */
ImageTypeNS DEFINITIONS ::=
BEGIN

IMPORTS 
Time FROM Time-Types
T-Int32, T-UInt32, T-Int8, T-UInt8, T-Boolean  FROM TASTE-BasicTypes 
T-Int64, T-UInt16, T-Double, T-Float, T-UInt64, T-String FROM TASTE-ExtendedTypes;

ImageMode ::= ENUMERATED 
	{
	mode-undefined, 
	mode-grayscale, 
	mode-rgb, 
	mode-uyvy, 
	mode-bgr, 
	mode-rgb32, 
	raw-modes, 
	mode-bayer, 
	mode-bayer-rggb, 
	mode-bayer-grbg, 
	mode-bayer-bggr, 
	mode-bayer-gbrg, 
	compressed-modes, 
	mode-pjpg, 
	mode-jpeg, 
	mode-png 
	}

-- 1024(width) x 768(height) x 3(bytes-per-pixel)
imageMaxBytes            T-UInt32 ::= 2359296
imageMaxRows             T-UInt32 ::= 768
imageMaxCols             T-UInt32 ::= 1024
imageMaxAttributes       T-UInt32 ::= 5


ImageType ::= SEQUENCE
	{
	image-time			Time,
	frame-identifier		T-String,
	data				SEQUENCE (SIZE (1..imageMaxBytes)) OF T-UInt8,
	width				T-UInt32,
	height				T-UInt32,
	row-size			T-UInt32,
	image-mode			ImageMode
	}

END
