/* --------------------------------------------------------------------------
*
* (C) Copyright …
*
* ---------------------------------------------------------------------------
*/

/*!
 * @file Geometry.asn
 * @date 17/11/2017
 * @author Alessandro Bianco
 */

/*!
 * @addtogroup BaseTypes
 * 
 * Specification of some common Geometric types.
 * 
 * 
 * @{
 */
GeometryNS DEFINITIONS ::=
BEGIN

IMPORTS
T-Int64, T-UInt16, T-Double, T-Float, T-UInt64, T-String FROM TASTE-ExtendedTypes;

Point2D ::= SEQUENCE
	{
	x	T-Float,
	y	T-Float
	}

Point3D ::= SEQUENCE
	{
	x	T-Float,
	y	T-Float,
	z	T-Float
	}

END

/** @} */
