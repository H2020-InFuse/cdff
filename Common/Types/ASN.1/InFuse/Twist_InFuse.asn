Twist-InFuse-Types DEFINITIONS ::=
BEGIN
IMPORTS
T-UInt32 FROM TASTE-BasicTypes
Time FROM Time-Types
TwistWithCovariance FROM TwistWithCovariance-Types;

-- Message version
twist-InFuse-Version T-UInt32 ::= 0

--- Definition of Twist_InFuse starts
Twist-InFuse ::= SEQUENCE
{
	-- Metadata

	msgVersion	T-UInt32,			-- Message version
	timeStamp	Time,				-- Time associated with twist

	-- Data

	twist	        TwistWithCovariance		-- Twist data
}

END
