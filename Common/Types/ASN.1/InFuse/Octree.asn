Octree-InFuse-Types DEFINITIONS ::=
BEGIN
IMPORTS
Pointcloud FROM Pointcloud-Types
T-Double FROM TASTE-ExtendedTypes
T-UInt32 FROM TASTE-BasicTypes;

-- Message version
octree-InFuse-Version T-UInt32 ::= 1

--- Definition of Octree starts
Octree ::= SEQUENCE
{
    resolution                     T-Double,
    pointCloud                     Pointcloud
}
--- Definition of Octree ends

END
