Image-InFuse-Types DEFINITIONS ::=
BEGIN
IMPORTS
T-UInt32 FROM TASTE-BasicTypes
T-Double, T-String FROM TASTE-ExtendedTypes
Matrix3d, VectorXd FROM Eigen-Types
Time FROM Time-Types
Pose-InFuse FROM Pose-InFuse-Types;

-- Message version
image-InFuse-Version    T-UInt32 ::= 1

--- Definition of enum Image-depth-t follows
Image-depth-t ::= ENUMERATED
{
  depth-8U,   -- 8-bit unsigned integers ( 0..255 )
  depth-8S,   -- 8-bit signed integers ( -128..127 )
  depth-16U,  -- 16-bit unsigned integers ( 0..65535 )
  depth-16S,  -- 16-bit signed integers ( -32768..32767 )
  depth-32S,  -- 32-bit signed integers ( -2147483648..2147483647 )
  depth-32F,  -- 32-bit floating-point numbers ( -FLT_MAX..FLT_MAX, INF, NAN )
  depth-64F   -- 64-bit floating-point numbers ( -DBL_MAX..DBL_MAX, INF, NAN )
}

--- Definition of enum image_type_t follows
Image-type-t ::= ENUMERATED
{
  type-UNDEF,
  type-GRAY,
  type-RGB,
  type-RGBA,
  type-BGR,
  type-BGRA,
  type-HSV,
  type-HLS,
  type-YUV,
  type-Lab,
  type-Luv,
  type-XYZ,
  type-YCrCb,
  type-Bayer-BG,
  type-Bayer-GB,
  type-Bayer-GR,
  type-Bayer-RG,
  type-JPEG,
  type-PNG
}

--- Definition of enum image_cameraModel_t follows
Image-cameraModel-t ::= ENUMERATED
{
  cam-UNDEF,
  cam-PINHOLE,
  cam-FISHEYE,
  cam-MAPS
}

--- Definition of enum image_pixelModel_t follows
Image-pixelModel-t ::= ENUMERATED
{
  -- Model of the function used to translate an X physical value into a f(X) pixel value
  pix-UNDEF, -- f(X) = X is assumed by default
  pix-POLY,  -- f(X) = a + b.X + c.X² + ...
  pix-DISP   -- [f(X) = a.X + b, c = baseline, d = minimum disparity value, e = maximum disparity value]
}

---  Image sizes (manually defined)
-- 1920(width) x 1080(height) x 8(bytes-per-pixel) x4(channels)
imageMaxBytes    T-UInt32 ::= 66355200
imageMaxRows     T-UInt32 ::= 1080
imageMaxCols     T-UInt32 ::= 1920

--- Definition of Image_InFuse starts
Image-InFuse ::= SEQUENCE
{
  -- Metadata
  msgVersion    T-UInt32,		    -- Message version
  rows				  T-UInt32,		    -- Height of the image
  cols				  T-UInt32,		    -- Width of the image
  channels      T-UInt32,       -- Number of matrix channels (1 to 4)
  depth         Image-depth-t,  -- Matrix element depth identifier
  type				  Image-type-t,   -- Image type
  lineStep      T-UInt32,       -- Number of bytes each matrix row occupies. The value should include the padding bytes at the end of each row, if any.

  -- Data
  data				  OCTET STRING (SIZE(0..imageMaxBytes))  -- Pixel data
}

--- Definition of ImageMetadata-InFuse Starts
ImageMetadata-InFuse ::= SEQUENCE
{
  msgVersion			               T-UInt32,		                        -- Message version
  sensorId			                 T-String,		                        -- Identifier for the sensor that produced the image
  timeStamp			                 Time,			                          -- Time at which the data has been acquired

  cameraMatrix 				           Matrix3d,                            -- Intrinsic camera calibration matrix
                                                                      -- [fx, s,  cx] with (fx, fy) the focal length in pixels
                                                                      -- [0,  fy, cy]      (cx, cy) the principal point offsets in pixels
                                                                      -- [0,  0,   1]      s the axis skew

  cameraModel                    Image-cameraModel-t,                 -- Camera model to use for correction
  distCoeffs                     VectorXd,                            -- Vector of distortion coefficients (k1, k2, p1, p2, k3, k4, k5, k6, s1, s2, s3, s4)
                                                                      -- k1-6 the radial distortion coefficients
                                                                      -- p1-2 the tangential distortion coefficients
                                                                      -- s1-4 the thin prism distortion coefficients

  pixelModel                     Image-pixelModel-t,                  -- Model of the function used to translate an X physical value into a f(X) pixel value
  pixelCoeffs                    VectorXd,                            -- Coefficients for the pixel model function

  errValue                       T-Double,                            -- Pixel error value (e.g. dead pixel value)

  hasFixedTransform              BOOLEAN,                             -- Is there a fixed transform attached to the image (robot base frame to fixed frame)
  pose-robotFrame-sensorFrame    Pose-InFuse,	                        -- Transform from sensor to robot frame
  pose-fixedFrame-robotFrame     Pose-InFuse                          -- Transform from robot frame to fixed frame (can be site frame or world frame). This is used mainly for DEBUG.
  -- poseList                       SEQUENCE(SIZE(0..10)) OF Pose-InFuse -- Transforms that can be relevant to use the image
}

--- Definition of ImageStamped-InFuse
ImageStamped-InFuse ::= SEQUENCE
{
  msgVersion			               T-UInt32,              -- Message version

  metadata                       ImageMetadata-InFuse,  -- Image Metadata
  image				                   Image-InFuse           -- Raw image
}

---  Definition ImagePair_InFuse Starts
ImagePair-InFuse   ::=
SEQUENCE
{
  -- Metadata
  msgVersion    T-UInt32,		          -- Message version
  baseline      T-Double,             -- Distance between the optical centers of the two cameras

  -- Data
  left				  ImageStamped-InFuse,  -- Left image
  right				  ImageStamped-InFuse   -- Right image

  -- TODO : ADD CORRECTION MATRIX
}

END
