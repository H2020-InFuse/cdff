----------------------------------------------------------------
--!   ASN file generated automatically by the SARGON ASN.1 generator -
--!  Date/time of generation: 2016/06/01 12:39:26
----------------------------------------------------------------
Pointcloud-Types DEFINITIONS ::=
BEGIN
IMPORTS T-Int32, T-UInt32, T-Int8, T-UInt8, T-Boolean  FROM TASTE-BasicTypes T-Int64, T-UInt16, T-Double, T-Float, T-UInt64, T-String FROM TASTE-ExtendedTypes Vector3d FROM Eigen-Types Time FROM Time-Types Vector4d FROM Eigen-Types Point FROM Point-Types TransformWithCovariance FROM TransformWithCovariance-Types;

---- Beginning of typedefs defined in the module: note that they could require to be adjusted manually 

---- END of typedefs defined in this module 


--- Size of the Pointcloud data
maxPointcloudSize T-UInt32 ::= 400000

--- Message version
pointCloud-Version T-UInt32 ::= 1


--- Point cloud metadata
PointCloud-Metadata ::=
SEQUENCE
{

    msgVersion			            T-UInt32,		-- Message version
    
    sensorId			            T-String,		-- Identifier for the sensor the produced the point cloud
    frameId				    T-String, 		-- Frame in which the point cloud is described 
    timeStamp			            Time,		-- Time at which the data has been acquired
    
    height				    T-UInt32,		-- Height of the point cloud
    width				    T-UInt32,		-- Width of the point cloud (1 if isOrdered is TRUE)
    
    
    isRegistered		            BOOLEAN,		-- Is there color info on the point cloud
    isOrdered			            BOOLEAN, 		-- Is the point cloud ordered
    hasFixedTransform                       BOOLEAN,            -- Is there a fixed transform attached to the point cloud (robot base frame to fixed frame)
    
    pose-robotFrame-sensorFrame             TransformWithCovariance,	-- Transform from sensor to robot frame
    pose-fixedFrame-robotFrame              TransformWithCovariance        -- Transform from robot frame to fixed frame (can be site frame or world frame). This is used mainly for DEBUG.

}

PointCloud-Data ::=
SEQUENCE 
{
    -- Geometrical data
    points				    SEQUENCE(SIZE(0..maxPointcloudSize)) OF Point,	
    -- Colors (empty if isRegitered is FALSE)
    colors				    SEQUENCE(SIZE(0..maxPointcloudSize)) OF Vector3d,	
    -- Intensity
    intensity                               SEQUENCE(SIZE(0..maxPointcloudSize)) OF T-Int32       

}


---  Definition POINTCLOUD Starts 
Pointcloud   ::= 
SEQUENCE
{
    metadata                                PointCloud-Metadata,
    data                                    PointCloud-Data
}

---  Definition POINTCLOUD Ends 
END
