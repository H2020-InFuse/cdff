----------------------------------------------------------------
--!   ASN file generated automatically by the SARGON ASN.1 generator -
--!  Date/time of generation: 2016/06/01 12:39:26
----------------------------------------------------------------
CompressedFrame-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes 
Time FROM Time-Types 
Frame-attrib-t FROM Frame-Types 
Frame-status-t FROM Frame-Types;


--- Definition of enum Frame-compressed-mode-t follows 
Frame-compressed-mode-t ::= ENUMERATED 
{ 
    mode-compressed-undefined, 
    mode-pjpg 
}


--- Sizes of the CompressedFrame data
maxCompressedFrameImageSize T-UInt32 ::= 262144
maxCompressedFrameImageAttributes T-UInt32 ::= 10


---  Definition of CompressedFrame follows 
CompressedFrame   ::= 
SEQUENCE
{
    ref-time         Time,
    received-time    Time,
    image            SEQUENCE (SIZE(1..maxCompressedFrameImageSize)) OF T-UInt8,
    attributes       SEQUENCE (SIZE(1..maxCompressedFrameImageAttributes)) OF Frame-attrib-t,
    rows             T-UInt32,
    cols             T-UInt32,
    frame-mode       Frame-compressed-mode-t,
    frame-status     Frame-status-t
}


END
