-- =====================================================================
--  FILE:  $URL$
-- =====================================================================
--  PROJECT:             :  SARGON
--  VERSION              :  $Revision$
--  LANGUAGE             :  ASN.1
--  AUTHOR               :  $LastChangedBy$ 
--  COPYRIGHT            :  AVOS - GMV,S.A.
--  COMPILER             :  asn2aadlPlus
--  CREATED              :  $CreationDate$
--  CLASS                :  -
--  LAST MODIFIED        :  $LastChangedDate$
--  GENERATED FROM MODEL :  -
--  ORIGINAL MODEL AUTHOR:  -
-- ---------------------------------------------------------------------
--  ASN.1 type definitions for the TASTE Vizkit3D functions.
-- ---------------------------------------------------------------------
--  HISTORY
--  $History$
-- =====================================================================

Vizkit3D-Types DEFINITIONS ::=
BEGIN

IMPORTS 
T-UInt32 FROM TASTE-BasicTypes;

-- String sizes
vizkit3dPathMaxSize T-UInt32 ::= 255
vizkit3dLabelMaxSize T-UInt32 ::= 31


-- File path, used for configuration files
VizkitFilePath ::= IA5String (SIZE (0..vizkit3dPathMaxSize))

-- Plugin label, identifies a plugin in a configuration file
VizkitPluginLabel ::= IA5String (SIZE (1..vizkit3dLabelMaxSize))

END
