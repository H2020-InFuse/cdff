Angle-Types DEFINITIONS ::=
BEGIN
IMPORTS T-Int32, T-UInt32, T-Int8, T-UInt8, T-Boolean  FROM TASTE-BasicTypes T-Int64, T-UInt16, T-Double, T-Float, T-UInt64, T-String FROM TASTE-ExtendedTypes;



---  Definition ANGLE Starts 
Angle   ::= 
SEQUENCE
{
--- angle in radians.
rad						T-Double
}

---  Definition ANGLE Ends 


---  Definition ANGLESEGMENT Starts 
AngleSegment   ::= 
SEQUENCE
{
--- Start angle of the segment in radians
startRad				T-Double,
--- Widht of the segment in radians
width					T-Double
}

---  Definition ANGLESEGMENT Ends 
END
