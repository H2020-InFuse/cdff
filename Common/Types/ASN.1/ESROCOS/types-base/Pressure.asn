----------------------------------------------------------------
--!   ASN file generated automatically by the SARGON ASN.1 generator -
--!  Date/time of generation: 2016/06/01 12:39:26
----------------------------------------------------------------
Pressure-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes 
Time FROM Time-Types;



---  Definition PRESSURE Starts 
Pressure   ::= 
SEQUENCE
{
    timestamp			Time,
    pascals             T-Double
}

---  Definition PRESSURE Ends 
END
