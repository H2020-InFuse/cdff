----------------------------------------------------------------
--!   ASN file generated automatically by the SARGON ASN.1 generator -
--!  Date/time of generation: 2016/06/01 12:39:26
----------------------------------------------------------------
Pose-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes 
Vector2d FROM Eigen-Types 
Vector3d FROM Eigen-Types 
Quaterniond FROM Eigen-Types;


---- Beginning of typedefs defined in the module: note that they could require to be adjusted manually 

---- Type: Position defined as base::Vector3d translated according to configuration
Position ::= Vector3d

---- Type: Position2D defined as base::Vector2d translated according to configuration
Position2D ::= Vector2d

---- Type: Orientation defined as base::Quaterniond translated according to configuration
Orientation ::= Quaterniond

---- END of typedefs defined in this module 


---  Definition POSEUPDATETHRESHOLD Starts 
PoseUpdateThreshold   ::= 
SEQUENCE
{
    distance				T-Double,
    angle					T-Double
}

---  Definition POSEUPDATETHRESHOLD Ends 


---  Definition POSE Starts 
Pose   ::= 
SEQUENCE
{
    pos				Position,
    orient			Orientation
}

---  Definition POSE Ends 


---  Definition POSE2D Starts 
Pose2D   ::= 
SEQUENCE
{
    position				Position2D,
    orientation				T-Double
}

---  Definition POSE2D Ends 
END
