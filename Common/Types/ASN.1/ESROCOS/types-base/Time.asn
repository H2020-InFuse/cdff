----------------------------------------------------------------
--!   ASN file generated automatically by the SARGON ASN.1 generator -
--!  Date/time of generation: 2016/06/01 12:39:26
----------------------------------------------------------------
Time-Types DEFINITIONS ::=
BEGIN
IMPORTS T-Int32, T-UInt32, T-Int8, T-UInt8, T-Boolean  FROM TASTE-BasicTypes T-Int64, T-UInt16, T-Double, T-Float, T-UInt64, T-String FROM TASTE-ExtendedTypes;


--- Definition of enum Resolution follows 

Resolution ::= ENUMERATED { 	 seconds, milliseconds, microseconds }

--- End Definition of enum Resolution

---  Definition TIME Starts 

---- Beginning of typedefs defined in the module: note that they could require to be adjusted manually 

---- END of typedefs defined in this module 
Time   ::= 
SEQUENCE
{
microseconds			T-Int64,
usecPerSec				T-Int32
}

---  Definition TIME Ends 
END
