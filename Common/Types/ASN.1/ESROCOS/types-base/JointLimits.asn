----------------------------------------------------------------
--!   ASN file generated automatically by the SARGON ASN.1 generator -
--!  Date/time of generation: 2016/06/01 12:39:26
----------------------------------------------------------------
JointLimits-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes
JointLimitRange FROM JointLimitRange-Types;


--- Size of the JointLimits data
maxJointLimitsSize T-UInt32 ::= 60


---  Definition JOINTLIMITS Starts 
JointLimits   ::= 
SEQUENCE
{
    vector-name     T-String,
    ranges          SEQUENCE (SIZE (1..maxJointLimitsSize)) OF JointLimitRange
}

---  Definition JOINTLIMITS Ends 
END
