----------------------------------------------------------------
--!   ASN file generated automatically by the SARGON ASN.1 generator -
--!  Date/time of generation: 2016/06/01 12:39:26
----------------------------------------------------------------
NamedVector-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes;


---- Beginning of typedefs defined in the module: note that they could require to be adjusted manually 

---- END of typedefs defined in this module 


--- The NamedVector type is used as base class for different Rock types; no ASN.1 equivalent is provided-
--- ---  Definition NAMEDVECTOR Starts 
--- NamedVector   ::= 
--- SEQUENCE
--- {
---     -- This attribute coverted from template.. please adjust it manually...
---     names					SEQUENCE (SIZE(1..60)) OF T-String,
---     -- FIXED: This attribute is defined as a template without conversion: please fix it+ manually...
---
---     -- Vector<T>
---     elements  T-Int32		
--- }
--- ---  Definition NAMEDVECTOR Ends 


---  Definition INVALIDNAME Starts 
InvalidName   ::= 
SEQUENCE
{
    nameString					T-String
}
---  Definition INVALIDNAME Ends 

END
