----------------------------------------------------------------
--!   ASN file generated automatically by the SARGON ASN.1 generator -
--!  Date/time of generation: 2016/06/01 12:39:26
----------------------------------------------------------------
JointState-Types DEFINITIONS ::=
BEGIN

IMPORTS 
T-Int32, T-UInt32, T-Int8, T-UInt8, T-Boolean  FROM TASTE-BasicTypes 
T-Int64, T-UInt16, T-Double, T-Float, T-UInt64, T-String FROM TASTE-ExtendedTypes;


--- Type MODE has been deleted: N/A to TASTE type

---  Definition JOINTSTATE Starts 

JointState   ::= 
SEQUENCE
{
    position				T-Double,
    speed					T-Float,
    effort					T-Float,
    raw						T-Float,
    acceleration			T-Float
}

---  Definition JOINTSTATE Ends 
END
