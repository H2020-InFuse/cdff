----------------------------------------------------------------
--!   ASN file generated automatically by the SARGON ASN.1 generator -
--!  Date/time of generation: 2016/06/01 12:39:26
----------------------------------------------------------------
Waypoint-Types DEFINITIONS ::=
BEGIN
IMPORTS T-Int32, T-UInt32, T-Int8, T-UInt8, T-Boolean  FROM TASTE-BasicTypes T-Int64, T-UInt16, T-Double, T-Float, T-UInt64, T-String FROM TASTE-ExtendedTypes Vector3d FROM Eigen-Types;



---  Definition WAYPOINT Starts 
Waypoint   ::= 
SEQUENCE
{
position				Vector3d,
heading					T-Double,
tol-position			T-Double,
tol-heading				T-Double
}

---  Definition WAYPOINT Ends 
END
