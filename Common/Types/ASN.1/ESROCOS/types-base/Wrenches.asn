----------------------------------------------------------------
--!   ASN file generated automatically by the SARGON ASN.1 generator -
--!  Date/time of generation: 2016/06/01 12:39:26
----------------------------------------------------------------
Wrenches-Types DEFINITIONS ::=
BEGIN
IMPORTS 
T-Int32, T-UInt32, T-Int8, T-UInt8, T-Boolean  FROM TASTE-BasicTypes 
T-Int64, T-UInt16, T-Double, T-Float, T-UInt64, T-String FROM TASTE-ExtendedTypes 
Time FROM Time-Types
Wrench FROM Wrench-Types;


--- Size of the Wrenches data
maxWrenchesSize T-UInt32 ::= 60

---  Definition WRENCHES Starts 
Wrenches   ::= 
SEQUENCE
{
    vector-name         T-String,
    timestamp           Time,
    wrenches            SEQUENCE (SIZE (1..maxWrenchesSize)) OF Wrench
}

---  Definition WRENCHES Ends 
END
