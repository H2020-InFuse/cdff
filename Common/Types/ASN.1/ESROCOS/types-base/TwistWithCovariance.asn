----------------------------------------------------------------
--!   ASN file generated automatically by the SARGON ASN.1 generator -
--!  Date/time of generation: 2016/06/01 12:39:26
----------------------------------------------------------------
TwistWithCovariance-Types DEFINITIONS ::=
BEGIN
IMPORTS T-Int32, T-UInt32, T-Int8, T-UInt8, T-Boolean  FROM TASTE-BasicTypes T-Int64, T-UInt16, T-Double, T-Float, T-UInt64, T-String FROM TASTE-ExtendedTypes Matrix4d FROM Eigen-Types Vector3d FROM Eigen-Types Covariance FROM Covariance-Types Time FROM Time-Types;



---  Definition TWISTWITHCOVARIANCE Starts 

---- Beginning of typedefs defined in the module: note that they could require to be adjusted manually 

twistWithCovariance-Version T-UInt32 ::= 0

---- END of typedefs defined in this module 

TwistWithCovariance-metadata ::=
SEQUENCE
{
    msgVersion      T-UInt32,
    timeStamp       Time
}

TwistWithCovariance-data   ::= 
SEQUENCE
{
    vel	            Vector3d,
    rot             Vector3d,
    cov             Covariance
}

TwistWithCovariance ::=
SEQUENCE
{
    metadata        TwistWithCovariance-metadata,
    data            TwistWithCovariance-data
}

---  Definition TWISTWITHCOVARIANCE Ends 
END
